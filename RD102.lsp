(defun ssp ()
  (setq sequenceStr (getstring "Please input the start pipe string ( end with enter):"))
  (setq strFor (substr sequenceStr 1 4))
  (setq sequence (ATOI (substr sequenceStr 5)))
  (setq pipeText (entsel))
  (while pipeText
    (setq textData (entget (car pipeText)))
    (setq oldr (assoc 1 textData))
    (setq pipeSplit (strSplit (cdr oldr)))
    (if (and (> sequence 0) (< sequence 10))
      (setq strNum (strcat "0" (ITOA sequence)))
      (setq strNum (ITOA sequence))
    )
    (setq newSequence (strcat strFor strNum))
    (setq newPipeText (strcat (nth 0 pipeSplit) newSequence (nth 2 pipeSplit) ))
    (setq newr (cons 1 newPipeText))
    (setq textData (subst newr oldr textData))
    (entmod textData)
    (setq sequence (+ 1 sequence))
    (setq pipeText (entsel))
  )
  (print "END")
  (prin1)
)
(defun strSplit (dataStr)
  (setq n (strlen dataStr))
  (princ n)
  (setq i 1)
  (setq twoLoc 0)
  (setq fourLoc 0)
  (setq sixLoc 0)
  (setq strList '()
        part    ""
  )
  (while (/= n 0)
    (if (= twoLoc 0)
      (progn
        (setq part (substr dataStr i 2))
        (if (wcmatch part "##")
          (progn
            (setq twoLoc i)
          )
        )
        (setq part (substr dataStr i 6))
        (if (wcmatch part "######")
          (progn
            (setq sixLoc i)
            (setq n 1)
          )
        )
      )
      (progn
        (setq part (substr dataStr i 4))
        (if (wcmatch part "####")
          (progn
            (setq fourLoc i)
            (setq n 1)
          )
        )
      )
    )
    (setq i (+ 1 i))
    (setq n (- n 1))
  )
  (if (and (/= twoLoc 0) (/= fourLoc 0))
    (progn
      (setq strList (cons (substr dataStr 1 (- twoLoc 1)) strList))
      (setq strList (cons (substr dataStr twoLoc (- (+ fourLoc 4) twoLoc)) strList))
      (setq strList (cons (substr dataStr (+ fourLoc 4)) strList))
    )
  )
  (if (/= sixLoc 0)
    (progn
      (setq strList (cons (substr dataStr 1 (- sixLoc 1)) strList))
      (setq strList (cons (substr dataStr sixLoc 6) strList))
      (setq strList (cons (substr dataStr (+ sixLoc 6)) strList))
    )
  )
  (reverse strList)
)
(defun ssv ()
  (setq start (getstring "Please input the start valve string ( end with enter):"))
  (setq startFormer (substr start 1 6))
  (setq num (ATOI (substr start 7 8)))
  (setq valveText (entsel))
  (while valveText
    (setq textData (entget (car valveText)))
    (setq oldr (assoc 1 textData))
    (if (and (> num 0) (< num 10))
      (setq strNum (strcat "0" (ITOA num)))
      (setq strNum (ITOA num))
    )
    (setq newr (cons 1 (strcat startFormer strNum)))
    (setq textData (subst newr oldr textData))
    (entmod textData)
    (setq num (+ 1 num))
    (setq valveText (entsel))
    (prin1)
  )
  (print "END")
  (prin1)
)
